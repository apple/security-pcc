-- Copyright © 2026 Apple Inc. All Rights Reserved.

-- APPLE INC.
-- PRIVATE CLOUD COMPUTE SOURCE CODE INTERNAL USE LICENSE AGREEMENT
-- PLEASE READ THE FOLLOWING PRIVATE CLOUD COMPUTE SOURCE CODE INTERNAL USE LICENSE AGREEMENT (“AGREEMENT”) CAREFULLY BEFORE DOWNLOADING OR USING THE APPLE SOFTWARE ACCOMPANYING THIS AGREEMENT(AS DEFINED BELOW). BY DOWNLOADING OR USING THE APPLE SOFTWARE, YOU ARE AGREEING TO BE BOUND BY THE TERMS OF THIS AGREEMENT. IF YOU DO NOT AGREE TO THE TERMS OF THIS AGREEMENT, DO NOT DOWNLOAD OR USE THE APPLE SOFTWARE. THESE TERMS AND CONDITIONS CONSTITUTE A LEGAL AGREEMENT BETWEEN YOU AND APPLE.
-- IMPORTANT NOTE: BY DOWNLOADING OR USING THE APPLE SOFTWARE, YOU ARE AGREEING ON YOUR OWN BEHALF AND/OR ON BEHALF OF YOUR COMPANY OR ORGANIZATION TO THE TERMS OF THIS AGREEMENT.
-- 1. As used in this Agreement, the term “Apple Software” collectively means and includes all of the Apple Private Cloud Compute materials provided by Apple here, including but not limited to the Apple Private Cloud Compute software, tools, data, files, frameworks, libraries, documentation, logs and other Apple-created materials. In consideration for your agreement to abide by the following terms, conditioned upon your compliance with these terms and subject to these terms, Apple grants you, for a period of ninety (90) days from the date you download the Apple Software, a limited, non-exclusive, non-sublicensable license under Apple’s copyrights in the Apple Software to download, install, compile and run the Apple Software internally within your organization only on a single Apple-branded computer you own or control, for the sole purpose of verifying the security and privacy characteristics of Apple Private Cloud Compute. This Agreement does not allow the Apple Software to exist on more than one Apple-branded computer at a time, and you may not distribute or make the Apple Software available over a network where it could be used by multiple devices at the same time. You may not, directly or indirectly, redistribute the Apple Software or any portions thereof. The Apple Software is only licensed and intended for use as expressly stated above and may not be used for other purposes or in other contexts without Apple's prior written permission. Except as expressly stated in this notice, no other rights or licenses, express or implied, are granted by Apple herein.
-- 2. The Apple Software is provided by Apple on an "AS IS" basis. APPLE MAKES NO WARRANTIES, EXPRESS OR IMPLIED, INCLUDING WITHOUT LIMITATION THE IMPLIED WARRANTIES OF NON-INFRINGEMENT, MERCHANTABILITY AND FITNESS FOR A PARTICULAR PURPOSE, REGARDING THE APPLE SOFTWARE OR ITS USE AND OPERATION ALONE OR IN COMBINATION WITH YOUR PRODUCTS, SYSTEMS, OR SERVICES. APPLE DOES NOT WARRANT THAT THE APPLE SOFTWARE WILL MEET YOUR REQUIREMENTS, THAT THE OPERATION OF THE APPLE SOFTWARE WILL BE UNINTERRUPTED OR ERROR-FREE, THAT DEFECTS IN THE APPLE SOFTWARE WILL BE CORRECTED, OR THAT THE APPLE SOFTWARE WILL BE COMPATIBLE WITH FUTURE APPLE PRODUCTS, SOFTWARE OR SERVICES. NO ORAL OR WRITTEN INFORMATION OR ADVICE GIVEN BY APPLE OR AN APPLE AUTHORIZED REPRESENTATIVE WILL CREATE A WARRANTY.
-- 3. IN NO EVENT SHALL APPLE BE LIABLE FOR ANY DIRECT, SPECIAL, INDIRECT, INCIDENTAL OR CONSEQUENTIAL DAMAGES (INCLUDING, BUT NOT LIMITED TO, PROCUREMENT OF SUBSTITUTE GOODS OR SERVICES; LOSS OF USE, DATA, OR PROFITS; OR BUSINESS INTERRUPTION) ARISING IN ANY WAY OUT OF THE USE, REPRODUCTION, COMPILATION OR OPERATION OF THE APPLE SOFTWARE, HOWEVER CAUSED AND WHETHER UNDER THEORY OF CONTRACT, TORT (INCLUDING NEGLIGENCE), STRICT LIABILITY OR OTHERWISE, EVEN IF APPLE HAS BEEN ADVISED OF THE POSSIBILITY OF SUCH DAMAGE.
-- 4. This Agreement is effective until terminated. Your rights under this Agreement will terminate automatically without notice from Apple if you fail to comply with any term(s) of this Agreement. Upon termination, you agree to cease all use of the Apple Software and destroy all copies, full or partial, of the Apple Software. This Agreement constitutes the entire understanding of the parties with respect to the subject matter contained herein, and supersedes all prior negotiations, representations, or understandings, written or oral. This Agreement will be governed and construed in accordance with the laws of the State of California, without regard to its choice of law rules.
-- You may report security issues about Apple products to product-security@apple.com, as described here: https://www.apple.com/support/security/. Non-security bugs and enhancement requests can be made via https://bugreport.apple.com as described here: https://developer.apple.com/bug-reporting/
-- EA1937
-- 10/02/2024

BEGIN
ReleaseV2 ::= SEQUENCE {
    version        INTEGER(2),
    appleSiliconV1 [0] AppleSiliconV1 OPTIONAL,
    gcpV1Workload  [1] GCPv1Workload OPTIONAL,
    gcpV1Platform  [2] GCPv1Platform OPTIONAL
}

-- aka Release (v1)
AppleSiliconV1 ::= SEQUENCE {
    version                 INTEGER(1),
    canonicalApTicket       OCTET STRING,
    canonicalCryptexTickets SET OF OCTET STRING,
    ...
    -- Additional fields should be OPTIONAL
    coprocessors            [0] SEQUENCE OF AppleSiliconV1 OPTIONAL
}

LinuxV1Measurements ::= SEQUENCE {
    -- Bowcaster and beyond
    ukiDigest         [0] OCTET STRING OPTIONAL, -- SHA384, digest of PE sans signature
    ovmfDigest        [1] OCTET STRING OPTIONAL, -- SHA384, only present in VMs

    -- Bowcaster & Vanguard
    nvidiaDriver      [2] NvidiaGPUMeasurement OPTIONAL, -- only present in workloadVMMeasurements

    -- Vanguard
    shimDigest        [3] OCTET STRING OPTIONAL, -- SHA384
    grubDigest        [4] OCTET STRING OPTIONAL, -- SHA384
    vmlinuzDigest     [5] OCTET STRING OPTIONAL, -- SHA384
    kernelCommandLine [6] UTF8String OPTIONAL
}

GCPv1Workload ::= SEQUENCE {
    workloadVMMeasurements      [0] LinuxV1Measurements OPTIONAL,
    keyProtectionVMMeasurements [1] LinuxV1Measurements OPTIONAL,
    hostMeasurements            [2] LinuxV1Measurements OPTIONAL,
    containerImageDigest        [3] UTF8String OPTIONAL, -- OCI digest format ("sha256:a2e12...")
    variant                     [4] UTF8String OPTIONAL  -- afm, adm, etc.
}

GCPv1Platform ::= SEQUENCE {
    titan      [0] OCTET STRING OPTIONAL, -- SHA256, EK certificate RW firmware hash (Titan chip)
    bmc        [1] OCTET STRING OPTIONAL, -- SHA256, EV_EFI_HCRTM_EVENT digest at PCR[0] (BMC firmware)
    bios       [2] OCTET STRING OPTIONAL, -- SHA256, Google DRTM event digest at PCR[17] (host BIOS)

    intelTDX   [3] IntelTDXPlatform OPTIONAL,
    nvidiaGPU  [4] NvidiaGPUMeasurement OPTIONAL,

    -- Vanguard
    ovmfDigest [5] OCTET STRING OPTIONAL -- SHA384, MRTD
}

IntelTDXPlatform ::= SEQUENCE {
    -- TDX Module (SEAM)
    seamDigest    [0] OCTET STRING,   -- SHA384, MRSEAM
    seamSigner    [1] OCTET STRING,   -- SHA384, MRSIGNERSEAM
    seamVersion   [2] INTEGER,        -- SEAMSVN

    -- Quoting Enclave (QE)
    qeDigest      [3] OCTET STRING,   -- SHA256, MRENCLAVE
    qeSigner      [4] OCTET STRING,   -- SHA256, MRSIGNER
    qeProductId   [5] INTEGER,        -- ISVPRODID
    qeVersion     [6] INTEGER,        -- ISVSVN

    -- Platform TCB
    teeTcbSvn     [7] OCTET STRING,   -- 16 bytes, TEE TCB SVN from TDX quote body
    fmspc         [8] OCTET STRING,   -- 6 bytes, Family-Model-Stepping-Platform-CustomSKU from PCK certificate
    sgxTcbCompSvn [9] OCTET STRING,   -- 16 bytes, SGX TCB Component SVNs from PCK certificate
    pcesvn        [10] INTEGER        -- Provisioning Certification Enclave SVN
}

NvidiaGPUMeasurement ::= SEQUENCE {
    product      [0] UTF8String,                  -- e.g. "GB100"
    version      [1] UTF8String,                  -- e.g. "590.48.01" (driver) or "97.00.D9.00.35" (VBIOS)
    blocks       [2] SEQUENCE OF NvidiaSPDMBlock  -- SPDM blocks contributed by this component; driver- vs VBIOS-attribution determined by location and NvidiaGPUMeasurement.driverSPDMIndices
}

NvidiaSPDMBlock ::= SEQUENCE {
    index  INTEGER,     -- SPDM measurement block index
    digest OCTET STRING -- SHA-384
}

-- Goes into an X509 extension of Apple Platform Certificate
GCPv1DeviceIdentityManifest ::= SEQUENCE {
    type                 INTEGER(1),
    googleIdentityDigest [0] OCTET STRING OPTIONAL,       -- won't exist until Bowcaster
    intelIdentityDigest  [1] OCTET STRING OPTIONAL,       -- digest of `PCKCertificate`
    nvidiaIdentityDigest [2] SET OF OCTET STRING OPTIONAL -- digest of leaf in `ConfidentialSpace_GpuInfo.attestationCertificateChain`
}
END
